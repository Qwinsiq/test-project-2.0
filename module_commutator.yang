module commutator{

namespace "commutator";
prefix com;
	container subscribers{
	config true;
	list subscriber{
		key number;
		leaf number{type string;}
		leaf userName{type string; config false;}
		leaf incomingNumber{type string;}
		leaf state{type enumeration{enum idle; enum busy; enum active;} default idle;}
	}
}
	notification statCall
	{
		leaf startTime{type string; mandatory true;}
		leaf abonentA{type string; mandatory true;}
		leaf abonentB{type string; mandatory true;}
		leaf duration{type string;}
	}
	
}
